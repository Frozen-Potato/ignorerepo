module _3gpp-common-qmcjob {
  yang-version 1.1;
  namespace "urn:3gpp:sa5:_3gpp-common-qmcjob";
  prefix "qmc3gpp";

  import _3gpp-common-top { prefix top3gpp; }
  import _3gpp-common-subnetwork { prefix subnet3gpp; }
  import _3gpp-common-yang-types { prefix types3gpp; }
  import _3gpp-common-yang-extensions { prefix yext3gpp; }
  import _3gpp-5g-common-yang-types { prefix types5g3gpp; }
  import _3gpp-common-managed-element { prefix me3gpp; }
  import _3gpp-common-trace { prefix trace3gpp; }
  import ietf-inet-types { prefix inet; }

  organization "3GPP SA5";
  contact "https://www.3gpp.org/DynaReport/TSG-WG--S5--officials.htm?Itemid=464";
  description "Quality of Experience Measurement Collection Job handling
    Copyright 2025, 3GPP Organizational Partners (ARIB, ATIS, CCSA, ETSI, TSDSI, 
    TTA, TTC). All rights reserved.";
  reference "3GPP TS 28.623
      Generic Network Resource Model (NRM)
      Integration Reference Point (IRP);
      Solution Set (SS) definitions

      3GPP TS 28.622
      Generic Network Resource Model (NRM)
      Integration Reference Point (IRP);
      Information Service (IS)";

  revision 2025-02-06 { reference CR-0508; }
  revision 2024-11-05 { reference CR-0480; }
  revision 2024-04-04 { reference CR-0334; } 
  revision 2023-09-18 { reference CR-0271 ; } 
  revision 2023-02-14 { reference "CR-0234"; }
  revision 2022-11-04 { reference "CR-0215"; }
  revision 2022-08-17 { reference "CR-0185"; }
  revision 2022-04-29 { reference "CR-0171"; }
  revision 2022-03-22 { reference "draftCR"; }
  revision 2022-01-06 { reference "CR-0142"; }
    
  grouping QMCJobGrp {
    leaf serviceType {
      description "Specifies an end user service type for QoE measurements.";
      mandatory true;
      type enumeration {
      enum DASH;
      enum MTSI;
      enum VR;
    }
    }

    list areaScope {
      key "idx";
      leaf idx { type uint32 ; }
      description "It defines the area scope of QoE, which is specified
       in clause 5.4 of TS 28.405.";   
      uses trace3gpp:AreaScopeGrp;      
    }

    leaf qoECollectionEntityAddress {
      type inet:ip-address;
      mandatory true;
      description "Specifies the address to which the QMC records shall be
        transferred.  Ipv4 or Ipv6 address(es) may be used.";
    }

    list pLMNTarget {
      max-elements 1;
      description "Defines the PLMN for which sessions shall be selected in 
        the network request session in case of area based QMC when several 
        PLMNs are supported in the RAN (this means that shared cells and not 
        shared cells are allowed for the specified PLMN. Furthermore, several 
        PLMNs can be used for not shared RAN cases as well as for shared RAN 
        cases.). Only the sessions may be selected where the PLMN that the 
        UE reports as selected PLMN is the same as the PLMN Target.";
      uses types3gpp:PLMNId;
      key "mcc mnc";
    }

    leaf qoETarget {
      type string;
      description "Specifies the target object of the QMC in case of 
        signalling based QMC.  The qoETarget attribute shall be able 
        to carry IMSI or SUPI.";
      mandatory true;
    }

    leaf qoEReference {
      type string;
      mandatory true;
      description "Identifies the QoE measurement collection job in the 
        Managed Elements and in the measurement collection entity.  The QoE
        reference shall be globally unique therefore it is composed as follows:
        MCC+MNC+QMC ID, where the MCC and MNC are coming with the QMC 
        activation request from the management system to identify one PLMN 
        containing the management system, and QMC ID is a 3 byte Octet String. 
        The QMC ID is generated by the management system or the operator.";
    }

    leaf jobId {
      type string;
      yext3gpp:inVariant;
      description "The jobId attribute presents the job identifier of a 
        QMCJob instance. The jobId can be used to associate  multiple QMCJob 
        instances. For example, it is possible to configure the same jobId 
        for multiple QMCJob instances required to produce the data 
        (e.g. Streaming services and MTSI reports) for a specific network 
        analysis.";
    }
    
    list sliceScope {
      description "Contains a list of S-NSSAIs (Single Network Slice Selection
        Assistance Information).  A Network Slice end to end is identified by
        S-NSSAI.";
      key "sd sst";
      uses types5g3gpp:SNssai;
    }

    leaf qMCConfigFile {
      type string;
      description "Provides a reference to a file including the parameters for 
        configuration of application layer measurements, known as Container
        for Application Layer Measurement Configuration.";
      mandatory true;
    }

    list mDTAlignmentInformation {
      key "idx";
      min-elements 1;
      max-elements 1;
      description "This parameter indicates the MDT measurements with which
        alignment of QoE measurement is required. This parameter is optional
        and is valid for NR only.";

      leaf idx { type uint32 ; }
      uses trace3gpp:TraceReferenceGrp ;
    }

    
    leaf-list availableRANqoEMetrics {
      type enumeration {
        enum APP_LAYER_BUFFER_LEVEL_LIST;
        enum PLAYOUT_DELAY_FOR_MEDIA_STARTUP;
      }
      max-elements 2;
      description "This parameter indicates available RAN visible QoE metrics
      to the gNB. This parameter is optional and is valid for NR only.";
    }

    leaf mBSCommunicationServiceType {
      type enumeration {
        enum BROADCAST;
        enum MULTICAST;
      }
      description "This attribute indicates which type of MBS communication 
        service the QoE measurement configuration pertains to.";
    }
  }
    
   grouping QMCJobSubTree {
   description "Helps with augmenting QMCJob into multple places.";
    list QMCJob {
      description "The QoE Measurement Collection provides capability for 
       collecting QoE information from:
       - UEs which are in the specified area in case of Management Based 
       Activation or 
       - an individual UE in case of Signalling Based Activation.
       The QoE Measurement Collection enables collection of application layer 
       measurements from the UE for specified end user service type. 
       The supported service types are:
       - Streaming services, see TS 26.247  
       - MTSI services, see TS 26.114 
       - VR services, see TS 26.118 
       A QMCJob instance represents the job for collecting QoE measurements 
       according to the job parameters. For details of the QoE measurement 
       collection configuration parameters see clause 5 of TS 28.405. 
       QMCJob instance can be name-contained by SubNetwork or ManagedElement. 
       A QMC Job is activated by creating a QMCJob object instance in the 
       producer. For details of Management Based Activation of QoE Measurement 
       Collection see clause 4.5 and for details of Signalling Based 
       Activation of QoE Measurement Collection see clause 4.6 of TS 28.405. 
       The attribute  pLMNTarget is only relevant when 
       Management Based Activation is used and the attribute qoETarget is 
       only relevant when Signalling Based Activation is used. All other 
       attributes are common for both Management Based Activation and 
       Signalling Based Activation.

       The areaScope attribute defines the area scope of QoE, which is 
       specified in clause 5.4 of TS 28.405.

       When a MnS consumer wishes to deactivate a QMC Job, the MnS consumer 
       shall delete the corresponding QMCJob instance. 
       NOTE:  If the reporting is ongoing, when a request to delete a QMCJob 
       is received, the reporting does not end. The QMCJob instance is deleted, 
       when the last reporting for the QMC Job expires.

       The jobId attribute presents the job identifier of a QMCJob instance. 
       jobId can be used to associate  multiple QMCJob instances. For example, 
       it is possible to configure the same jobId value for multiple QMCJob 
       instances required to produce the data (e.g. Streaming services and 
       MTSI reports) for a specific network analysis.";
      key id;
      uses top3gpp:Top_Grp;
      container attributes {
        uses QMCJobGrp;
      }
    }
  }
  
   augment "/subnet3gpp:SubNetwork" {
        uses QMCJobSubTree;
   }

   augment "/me3gpp:ManagedElement" {
        uses QMCJobSubTree;
   }
}
